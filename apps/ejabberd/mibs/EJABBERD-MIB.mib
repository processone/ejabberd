EJABBERD-MIB DEFINITIONS ::= BEGIN

IMPORTS
    MODULE-IDENTITY, OBJECT-TYPE, NOTIFICATION-TYPE,
    enterprises, Counter64, Gauge32
        FROM SNMPv2-SMI
    DisplayString
        FROM SNMPv2-TC
    MODULE-COMPLIANCE, OBJECT-GROUP, NOTIFICATION-GROUP
        FROM SNMPv2-CONF
    ;

ejabberdRegModule MODULE-IDENTITY
    LAST-UPDATED "201107281122Z"
    ORGANIZATION "erlang-solutions.com"
    CONTACT-INFO "erlang-solutions.com"
    DESCRIPTION
	"The root MIB module for ejabberd"
    ::= {ejabberdMIB 3}


ejabberd		OBJECT IDENTIFIER ::= {enterprises 40005}
ejabberdMIB	    OBJECT IDENTIFIER ::= {ejabberd 1}

ejabberdMIBConformance	OBJECT IDENTIFIER ::= {ejabberdMIB 1}
ejabberdMIBObjects		OBJECT IDENTIFIER ::= {ejabberdMIB 2}

-- Managed Objects
ejabberdSystemStats	OBJECT IDENTIFIER ::= {ejabberdMIBObjects 1}

-- Features
ejabberdGeneral     OBJECT IDENTIFIER ::= {ejabberdSystemStats 1}
ejabberdCore        OBJECT IDENTIFIER ::= {ejabberdSystemStats 2}
ejabberdModRoster   OBJECT IDENTIFIER ::= {ejabberdSystemStats 3}
ejabberdModRegister OBJECT IDENTIFIER ::= {ejabberdSystemStats 4}
ejabberdModPrivacy  OBJECT IDENTIFIER ::= {ejabberdSystemStats 5}

-- General
generalUptime	OBJECT-TYPE
    SYNTAX	Counter64
    MAX-ACCESS	read-only
    STATUS	current
    DESCRIPTION
	"System's uptime (in seconds)"
    ::= {ejabberdGeneral 1}

generalNodeName	OBJECT-TYPE
    SYNTAX	DisplayString
    MAX-ACCESS	read-only
    STATUS	current
    DESCRIPTION
	"The name of the node"
    ::= {ejabberdGeneral 2}

-- Core
ejabberdSession     OBJECT IDENTIFIER ::= {ejabberdCore 1}
ejabberdC2s         OBJECT IDENTIFIER ::= {ejabberdCore 2}
ejabberdRouter      OBJECT IDENTIFIER ::= {ejabberdCore 3}

-- Session
sessionCount 		OBJECT-TYPE
    SYNTAX	Gauge32
    MAX-ACCESS	read-only
    STATUS	current
    DESCRIPTION
	"Number of sessions on this node"
    ::= {ejabberdSession 1}

globalSessionCount  OBJECT-TYPE
    SYNTAX Gauge32
    MAX-ACCESS read-only
    STATUS current
    DESCRIPTION
    "Number of sessions in the cluster"
    ::= {ejabberdSession 2}

globalUniqueSessionCount OBJECT-TYPE
    SYNTAX Gauge32
    MAX-ACCESS read-only
    STATUS current
    DESCRIPTION
    "Number of unique sessions in the cluster"
    ::= {ejabberdSession 3}

sessionAuthFails	OBJECT-TYPE
   SYNTAX	Counter64
    MAX-ACCESS	read-only
    STATUS	current
    DESCRIPTION
	"Number of authentication failures on login"
    ::= {ejabberdSession 4}

sessionAuthAnonymous	OBJECT-TYPE
   SYNTAX	Counter64
    MAX-ACCESS	read-only
    STATUS	current
    DESCRIPTION
	"Number of anonymous connections"
    ::= {ejabberdSession 5}

sessionSuccessfulLogins	OBJECT-TYPE
    SYNTAX	Counter64
    MAX-ACCESS	read-only
    STATUS	current
    DESCRIPTION
	"Number of successful login attempts"
    ::= {ejabberdSession 6}

sessionLogouts		OBJECT-TYPE
    SYNTAX 	Counter64
    MAX-ACCESS	read-only
    STATUS	current
    DESCRIPTION
	"Number of logouts"
    ::= {ejabberdSession 7}

sessionAuthFailsW	OBJECT-TYPE
   SYNTAX	Gauge32
    MAX-ACCESS	read-only
    STATUS	current
    DESCRIPTION
	"Number of authentication failures on login (window)"
    ::= {ejabberdSession 8}

sessionAuthAnonymousW	OBJECT-TYPE
   SYNTAX	Gauge32
    MAX-ACCESS	read-only
    STATUS	current
    DESCRIPTION
	"Number of anonymous connections (window)"
    ::= {ejabberdSession 9}

sessionSuccessfulLoginsW	OBJECT-TYPE
    SYNTAX	Gauge32
    MAX-ACCESS	read-only
    STATUS	current
    DESCRIPTION
	"Number of successful login attempts (window)"
    ::= {ejabberdSession 10}

sessionLogoutsW		OBJECT-TYPE
    SYNTAX 	Gauge32
    MAX-ACCESS	read-only
    STATUS	current
    DESCRIPTION
	"Number of logouts (window)"
    ::= {ejabberdSession 11}

-- C2s
xmppMessageSent	OBJECT-TYPE
    SYNTAX	Counter64
    MAX-ACCESS	read-only
    STATUS	current
    DESCRIPTION
	"Number of XMPP message stanzas sent by the users"
    ::= {ejabberdC2s 1}

xmppMessageReceived	OBJECT-TYPE
    SYNTAX	Counter64
    MAX-ACCESS	read-only
    STATUS	current
    DESCRIPTION
	"Number of XMPP message stanzas received by the users"
    ::= {ejabberdC2s 2}

xmppMessageBounced	OBJECT-TYPE
    SYNTAX	Counter64
    MAX-ACCESS	read-only
    STATUS	current
    DESCRIPTION
	"Number of XMPP messages bounced"
    ::= {ejabberdC2s 3}

xmppPresenceSent	OBJECT-TYPE
    SYNTAX 	Counter64
    MAX-ACCESS	read-only
    STATUS	current
    DESCRIPTION
	"Number of XMPP presence stanzas sent by the users"
    ::= {ejabberdC2s 4}

xmppPresenceReceived	OBJECT-TYPE
    SYNTAX	Counter64
    MAX-ACCESS	read-only
    STATUS	current
    DESCRIPTION
	"Number of XMPP presence stanzas received by the users"
    ::= {ejabberdC2s 5}

xmppIqSent		OBJECT-TYPE
    SYNTAX	Counter64
    MAX-ACCESS	read-only
    STATUS	current
    DESCRIPTION
	"Number of XMPP iq stanzas sent by the users"
    ::= {ejabberdC2s 6}

xmppIqReceived		OBJECT-TYPE
    SYNTAX	Counter64
    MAX-ACCESS	read-only
    STATUS	current
    DESCRIPTION
	"Number of XMPP iq stanzas received by the users"
    ::= {ejabberdC2s 7}

xmppStanzaSent		OBJECT-TYPE
    SYNTAX	Counter64
    MAX-ACCESS	read-only
    STATUS	current
    DESCRIPTION
	"Number of XMPP stanzas sent by the users"
    ::= {ejabberdC2s 8}

xmppStanzaReceived	OBJECT-TYPE
    SYNTAX	Counter64
    MAX-ACCESS	read-only
    STATUS	current
    DESCRIPTION
	"Number of XMPP stanzas received by the users"
    ::= {ejabberdC2s 9}

xmppStanzaDropped	OBJECT-TYPE
    SYNTAX	Counter64
    MAX-ACCESS	read-only
    STATUS	current
    DESCRIPTION
	"Number of XMPP stanzas droped by router"
    ::= {ejabberdC2s 10}

xmppErrorTotal	OBJECT-TYPE
    SYNTAX	Counter64
    MAX-ACCESS	read-only
    STATUS	current
    DESCRIPTION
	"Number of errors generated by server"
    ::= {ejabberdC2s 11}

xmppErrorBadRequest	OBJECT-TYPE
    SYNTAX	Counter64
    MAX-ACCESS	read-only
    STATUS	current
    DESCRIPTION
	"Number of errors caused by bad requests"
    ::= {ejabberdC2s 12}

xmppErrorIq	OBJECT-TYPE
    SYNTAX	Counter64
    MAX-ACCESS	read-only
    STATUS	current
    DESCRIPTION
	"Number of errors caused by iq stanzas"
    ::= {ejabberdC2s 13}

xmppErrorMessage OBJECT-TYPE
    SYNTAX	Counter64
    MAX-ACCESS	read-only
    STATUS	current
    DESCRIPTION
	"Number of errors caused by message stanzas"
    ::= {ejabberdC2s 14}

xmppErrorPresence	OBJECT-TYPE
    SYNTAX	Counter64
    MAX-ACCESS	read-only
    STATUS	current
    DESCRIPTION
	"Number of errors caused by presence stanzas"
    ::= {ejabberdC2s 15}

xmppIqTimeouts	OBJECT-TYPE
    SYNTAX	Counter64
    MAX-ACCESS	read-only
    STATUS	current
    DESCRIPTION
	"Number of timeouts"
    ::= {ejabberdC2s 16}

xmppMessageSentW	OBJECT-TYPE
    SYNTAX	Gauge32
    MAX-ACCESS	read-only
    STATUS	current
    DESCRIPTION
	"Number of XMPP message stanzas sent by the users (window)"
    ::= {ejabberdC2s 17}

xmppMessageReceivedW	OBJECT-TYPE
    SYNTAX	Gauge32
    MAX-ACCESS	read-only
    STATUS	current
    DESCRIPTION
	"Number of XMPP message stanzas received by the users (window)"
    ::= {ejabberdC2s 18}

xmppPresenceSentW	OBJECT-TYPE
    SYNTAX 	Gauge32
    MAX-ACCESS	read-only
    STATUS	current
    DESCRIPTION
	"Number of XMPP presence stanzas sent by the users (window)"
    ::= {ejabberdC2s 19}

xmppPresenceReceivedW	OBJECT-TYPE
    SYNTAX	Gauge32
    MAX-ACCESS	read-only
    STATUS	current
    DESCRIPTION
	"Number of XMPP presence stanzas received by the users (window)"
    ::= {ejabberdC2s 20}

xmppIqSentW		OBJECT-TYPE
    SYNTAX	Gauge32
    MAX-ACCESS	read-only
    STATUS	current
    DESCRIPTION
	"Number of XMPP iq stanzas sent by the users (window)"
    ::= {ejabberdC2s 21}

xmppIqReceivedW		OBJECT-TYPE
    SYNTAX	Gauge32
    MAX-ACCESS	read-only
    STATUS	current
    DESCRIPTION
	"Number of XMPP iq stanzas received by the users (window)"
    ::= {ejabberdC2s 22}

xmppStanzaSentW		OBJECT-TYPE
    SYNTAX	Gauge32
    MAX-ACCESS	read-only
    STATUS	current
    DESCRIPTION
	"Number of XMPP stanzas sent by the users (window)"
    ::= {ejabberdC2s 23}

xmppStanzaReceivedW	OBJECT-TYPE
    SYNTAX	Gauge32
    MAX-ACCESS	read-only
    STATUS	current
    DESCRIPTION
	"Number of XMPP stanzas received by the users (window)"
    ::= {ejabberdC2s 24}

xmppErrorTotalW	OBJECT-TYPE
    SYNTAX	Gauge32
    MAX-ACCESS	read-only
    STATUS	current
    DESCRIPTION
	"Number of errors generated by server (window)"
    ::= {ejabberdC2s 25}

xmppStanzaCount	OBJECT-TYPE
    SYNTAX	Counter64
    MAX-ACCESS	read-only
    STATUS	current
    DESCRIPTION
	"Number of all XMPP stanzas passing through the server"
    ::= {ejabberdC2s 26}

-- Router
routerRegisteredPathsTable	OBJECT-TYPE
    SYNTAX	SEQUENCE OF RouteEntry
    MAX-ACCESS	not-accessible
    STATUS	current
    DESCRIPTION
	"Table for registered routes"
    ::= {ejabberdRouter 1}

routerRegisteredPathEntry	OBJECT-TYPE
    SYNTAX	RouteEntry
    MAX-ACCESS	not-accessible
    STATUS	current
    DESCRIPTION
	"A conceptual row for routerRegisteredPathsTable"
    INDEX	{routeTo}
    ::= {routerRegisteredPathsTable 1}

RouteEntry ::= SEQUENCE {
    routeTo      DisplayString,
    routeNum     Gauge32
}

routeTo	OBJECT-TYPE
    SYNTAX	DisplayString
    MAX-ACCESS	read-only
    STATUS	current
    DESCRIPTION
	"Domain to which packets will be routed"
    ::= {routerRegisteredPathEntry 1}

routeNum	OBJECT-TYPE
    SYNTAX	Gauge32
    MAX-ACCESS	read-only
    STATUS	current
    DESCRIPTION
	"Number of routes"
    ::= {routerRegisteredPathEntry 2}


-- ModRoster
modRosterSets	OBJECT-TYPE
    SYNTAX	Counter64
    MAX-ACCESS	read-only
    STATUS	current
    DESCRIPTION
	"Number of roster sets"
    ::= {ejabberdModRoster 1}

modRosterGets	OBJECT-TYPE
    SYNTAX	Counter64
    MAX-ACCESS	read-only
    STATUS	current
    DESCRIPTION
	"Number of roster gets"
    ::= {ejabberdModRoster 2}

modPresenceSubscriptions	OBJECT-TYPE
    SYNTAX	Counter64
    MAX-ACCESS	read-only
    STATUS	current
    DESCRIPTION
	"Number of subscriptions - presence subscribe stanzas"
    ::= {ejabberdModRoster 3}

modPresenceUnsubscriptions	OBJECT-TYPE
    SYNTAX	Counter64
    MAX-ACCESS	read-only
    STATUS	current
    DESCRIPTION
	"Number of unsubscriptions - presence unsubscribe stanzas"
    ::= {ejabberdModRoster 4}

modRosterPush	OBJECT-TYPE
    SYNTAX	Counter64
    MAX-ACCESS	read-only
    STATUS	current
    DESCRIPTION
	"Number of roster pushes"
    ::= {ejabberdModRoster 5}

modRosterSize	OBJECT-TYPE
    SYNTAX	Gauge32
    MAX-ACCESS	read-only
    STATUS	current
    DESCRIPTION
	"Average roster size"
    ::= {ejabberdModRoster 6}

modRosterGroups	OBJECT-TYPE
    SYNTAX	Gauge32
    MAX-ACCESS	read-only
    STATUS	current
    DESCRIPTION
	"Average number of roster groups"
    ::= {ejabberdModRoster 7}

modRosterSetsW	OBJECT-TYPE
    SYNTAX	Gauge32
    MAX-ACCESS	read-only
    STATUS	current
    DESCRIPTION
	"Number of roster sets (window)"
    ::= {ejabberdModRoster 8}

modRosterGetsW	OBJECT-TYPE
    SYNTAX	Gauge32
    MAX-ACCESS	read-only
    STATUS	current
    DESCRIPTION
	"Number of roster gets (window)"
    ::= {ejabberdModRoster 9}

modPresenceSubscriptionsW	OBJECT-TYPE
    SYNTAX	Gauge32
    MAX-ACCESS	read-only
    STATUS	current
    DESCRIPTION
	"Number of subscriptions - presence subscribe stanzas (window)"
    ::= {ejabberdModRoster 10}

modPresenceUnsubscriptionsW	OBJECT-TYPE
    SYNTAX	Gauge32
    MAX-ACCESS	read-only
    STATUS	current
    DESCRIPTION
	"Number of unsubscriptions - presence unsubscribe stanzas (window)"
    ::= {ejabberdModRoster 11}

modRosterPushW	OBJECT-TYPE
    SYNTAX	Gauge32
    MAX-ACCESS	read-only
    STATUS	current
    DESCRIPTION
	"Number of roster pushes (window)"
    ::= {ejabberdModRoster 12}

-- modRegister

modRegisterCount    OBJECT-TYPE
    SYNTAX	Counter64
    MAX-ACCESS	read-only
    STATUS	current
    DESCRIPTION
	"Number of registrations"
    ::= {ejabberdModRegister 1}

modUnregisterCount  OBJECT-TYPE
    SYNTAX	Counter64
    MAX-ACCESS	read-only
    STATUS	current
    DESCRIPTION
	"Number of deregistrations"
    ::= {ejabberdModRegister 2}

modRegisterUserCount  OBJECT-TYPE
    SYNTAX	Gauge32
    MAX-ACCESS	read-only
    STATUS	current
    DESCRIPTION
	"Number of registered users"
    ::= {ejabberdModRegister 3}

modRegisterCountW    OBJECT-TYPE
    SYNTAX	Gauge32
    MAX-ACCESS	read-only
    STATUS	current
    DESCRIPTION
	"Number of registrations (window)"
    ::= {ejabberdModRegister 4}

modUnregisterCountW  OBJECT-TYPE
    SYNTAX	Gauge32
    MAX-ACCESS	read-only
    STATUS	current
    DESCRIPTION
	"Number of deregistrations (window)"
    ::= {ejabberdModRegister 5}

-- modPrivacy
modPrivacySets	OBJECT-TYPE
    SYNTAX	Counter64
    MAX-ACCESS	read-only
    STATUS	current
    DESCRIPTION
	"Number of privacy list sets"
    ::= {ejabberdModPrivacy 1}

modPrivacySetsActive	OBJECT-TYPE
    SYNTAX	Counter64
    MAX-ACCESS	read-only
    STATUS	current
    DESCRIPTION
	"Number of privacy active list sets"
    ::= {ejabberdModPrivacy 2}

modPrivacySetsDefault	OBJECT-TYPE
    SYNTAX	Counter64
    MAX-ACCESS	read-only
    STATUS	current
    DESCRIPTION
	"Number of privacy default list sets"
    ::= {ejabberdModPrivacy 3}

modPrivacyPush	OBJECT-TYPE
    SYNTAX	Counter64
    MAX-ACCESS	read-only
    STATUS	current
    DESCRIPTION
	"Number of privacy list pushes"
    ::= {ejabberdModPrivacy 4}

modPrivacyGets	OBJECT-TYPE
    SYNTAX	Counter64
    MAX-ACCESS	read-only
    STATUS	current
    DESCRIPTION
	"Number of privacy list gets"
    ::= {ejabberdModPrivacy 5}

modPrivacyStanzaBlocked	OBJECT-TYPE
    SYNTAX	Counter64
    MAX-ACCESS	read-only
    STATUS	current
    DESCRIPTION
	"Number of stanza blocked by mod_privacy"
    ::= {ejabberdModPrivacy 6}

modPrivacyListLength	OBJECT-TYPE
    SYNTAX	Gauge32
    MAX-ACCESS	read-only
    STATUS	current
    DESCRIPTION
	"Average privacy lists length"
    ::= {ejabberdModPrivacy 7}

modPrivacySetsW	OBJECT-TYPE
    SYNTAX	Gauge32
    MAX-ACCESS	read-only
    STATUS	current
    DESCRIPTION
	"Number of privacy list sets (window)"
    ::= {ejabberdModPrivacy 8}

modPrivacySetsActiveW	OBJECT-TYPE
    SYNTAX	Gauge32
    MAX-ACCESS	read-only
    STATUS	current
    DESCRIPTION
	"Number of privacy active list sets (window)"
    ::= {ejabberdModPrivacy 9}

modPrivacySetsDefaultW	OBJECT-TYPE
    SYNTAX	Gauge32
    MAX-ACCESS	read-only
    STATUS	current
    DESCRIPTION
	"Number of privacy default list sets (window)"
    ::= {ejabberdModPrivacy 10}

modPrivacyPushW	OBJECT-TYPE
    SYNTAX	Gauge32
    MAX-ACCESS	read-only
    STATUS	current
    DESCRIPTION
	"Number of privacy list pushes (window)"
    ::= {ejabberdModPrivacy 11}

modPrivacyGetsW	OBJECT-TYPE
    SYNTAX	Gauge32
    MAX-ACCESS	read-only
    STATUS	current
    DESCRIPTION
	"Number of privacy list gets (window)"
    ::= {ejabberdModPrivacy 12}

modPrivacyStanzaAll	OBJECT-TYPE
    SYNTAX	Counter64
    MAX-ACCESS	read-only
    STATUS	current
    DESCRIPTION
	"Number of all stanzas passing through mod_privacy"
    ::= {ejabberdModPrivacy 13}

-- Conformance information
ejabberdMIBCompliances	OBJECT IDENTIFIER ::= {ejabberdMIBConformance 1}
ejabberdMIBGroups		OBJECT IDENTIFIER ::= {ejabberdMIBConformance 2}

ejabberdBasicCompliance	MODULE-COMPLIANCE
    STATUS	current
    DESCRIPTION
        "The compliance statement for SNMPv2 entities which
        implement the OTP-MIB."
    MODULE  -- this module
        MANDATORY-GROUPS {
                          monitorGroup
                         }
    ::= {ejabberdMIBCompliances 1}

monitorGroup OBJECT-GROUP
    OBJECTS {
    generalUptime,
    generalNodeName,
    sessionCount,
    globalSessionCount,
    globalUniqueSessionCount,
    sessionSuccessfulLogins,
    sessionAuthAnonymous,
    sessionAuthFails,
    sessionLogouts,
    sessionSuccessfulLoginsW,
    sessionAuthAnonymousW,
    sessionAuthFailsW,
    sessionLogoutsW,
    xmppMessageSent,
    xmppMessageReceived,
    xmppMessageBounced,
    xmppPresenceSent,
    xmppPresenceReceived,
    xmppIqSent,
    xmppIqReceived,
    xmppStanzaSent,
    xmppStanzaReceived,
    xmppStanzaDropped,
    xmppStanzaCount,
    xmppErrorTotal,
    xmppErrorBadRequest,
    xmppErrorIq,
    xmppErrorMessage,
    xmppErrorPresence,
    xmppIqTimeouts,
    xmppMessageSentW,
    xmppMessageReceivedW,
    xmppPresenceSentW,
    xmppPresenceReceivedW,
    xmppIqSentW,
    xmppIqReceivedW,
    xmppStanzaSentW,
    xmppStanzaReceivedW,
    xmppErrorTotalW,
    routeTo,
    routeNum,
    modRosterSets,
    modRosterGets,
    modPresenceSubscriptions,
    modPresenceUnsubscriptions,
    modRosterPush,
    modRosterSetsW,
    modRosterGetsW,
    modPresenceSubscriptionsW,
    modPresenceUnsubscriptionsW,
    modRosterPushW,
    modRosterSize,
    modRosterGroups,
    modRegisterCount,
    modUnregisterCount,
    modRegisterCountW,
    modUnregisterCountW,
    modRegisterUserCount,
    modPrivacySets,
    modPrivacySetsActive,
    modPrivacySetsDefault,
    modPrivacyPush,
    modPrivacyGets,
    modPrivacySetsW,
    modPrivacySetsActiveW,
    modPrivacySetsDefaultW,
    modPrivacyPushW,
    modPrivacyGetsW,
    modPrivacyStanzaBlocked,
    modPrivacyStanzaAll,
    modPrivacyListLength
    }
    STATUS current
    DESCRIPTION
        "A collection of objects providing basic instrumentation
        of the ejabberd runtime system."
    ::= {ejabberdMIBGroups 1}

END
